FME workspace CallGeocoder_2.fmw

Parameters:
- AddressAttr = AddressLine1   # Address
- CityAttr = City   # City
- ProvinceAttr = StateProvince   # Province/State
- PostalCodeAttr =   # Postal Code/Zip
- CountryAttr =   # Country
- SourceDataset = /Users/nhildebrand/Downloads/SampleFile (13).csv   # Source CSV (Comma Separated Value) File(s)

Readers:
- CSV2_1: CSV2 from $(SourceDataset)

Writers:
- GEOJSON_1: GEOJSON to $(FME_DATA_REPOSITORY)GeocodedResults.json

Note: Read uploaded CSV file from user. / Reader is restricted to a maximum / of 50 records.
CSV (reader CSV2_1)
    attributes: HallNumber string, Name string, Address string, PhoneNumber string, Engine string, Ladder string, PostalCode string, Country string, City string, Province string
    -> AttributeCreator
AttributeCreator
    ATTR_TABLE:
      SET_TO _addr = FME_CONDITIONAL:DEFAULT_VALUE'@Value($(AddressAttr))'BOOL_OP;OR;COMPOSITE_TEST;<Unused>;TEST $(AddressAttr) ATTRIBUTE_IS_EMPTY _FME_BLANK_STRING_;TEST $(AddressAttr) ATTRIBUTE_IS_MISSING _FME_BLANK_STRING_''FME_NUM_CONDITIONS2___
      SET_TO _postal = FME_CONDITIONAL:DEFAULT_VALUE'@Value($(PostalCodeAttr))'BOOL_OP;OR;COMPOSITE_TEST;<Unused>;TEST $(PostalCodeAttr) ATTRIBUTE_IS_EMPTY _FME_BLANK_STRING_;TEST $(PostalCodeAttr) ATTRIBUTE_IS_MISSING _FME_BLANK_STRING_''FME_NUM_CONDITIONS2___
      SET_TO _country = FME_CONDITIONAL:DEFAULT_VALUE'@Value($(CountryAttr))'BOOL_OP;OR;COMPOSITE_TEST;<Unused>;TEST $(CountryAttr) ATTRIBUTE_IS_MISSING _FME_BLANK_STRING_;TEST $(CountryAttr) ATTRIBUTE_IS_EMPTY _FME_BLANK_STRING_''FME_NUM_CONDITIONS2___
      SET_TO _city = FME_CONDITIONAL:DEFAULT_VALUE'@Value($(CityAttr))'BOOL_OP;OR;COMPOSITE_TEST;<Unused>;TEST $(CityAttr) ATTRIBUTE_IS_EMPTY _FME_BLANK_STRING_;TEST $(CityAttr) ATTRIBUTE_IS_MISSING _FME_BLANK_STRING_''FME_NUM_CONDITIONS2___
      SET_TO _province = FME_CONDITIONAL:DEFAULT_VALUE'@Value($(ProvinceAttr))'BOOL_OP;OR;COMPOSITE_TEST;<Unused>;TEST $(ProvinceAttr) ATTRIBUTE_IS_EMPTY _FME_BLANK_STRING_;TEST $(ProvinceAttr) ATTRIBUTE_IS_MISSING _FME_BLANK_STRING_''FME_NUM_CONDITIONS2___
    -> AttributeCreator_2
AttributeCreator_2
    ATTR_TABLE = SET_TO full_address = @Value(_addr), @Value(_city), @Value(_province), @Value(_country)
    -> Geocoder
Geocoder
    GEOCODING_SERVICE = OpenStreetMap
    THREADS = 4
    TIMEOUT = 60
    -> GeocodedResults (writer GEOJSON_1)
    <REJECTED> -> Terminator
GeocodedResults (writer GEOJSON_1)
Terminator
    MESSAGE:
      There was an error geocoding one or more of your addresses.

      Message: "@Value(fme_rejection_code)"
